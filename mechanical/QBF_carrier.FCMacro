import FreeCAD as App
import Part
from pathlib import Path
import json

ROOT = Path(__file__).resolve().parent
GEOMETRY = json.loads((ROOT.parent / 'ergogen-kikad/generated/board_geometry.json').read_text())
W, H, GAP = GEOMETRY['width'], GEOMETRY['height'], 4.0
FLOOR, SLOT_LOW, SLOT_HIGH, TOP = 2.5, 17.0, 21.5, 22.2


def box(x, y, z, dx, dy, dz):
    return Part.makeBox(dx, dy, dz, App.Vector(x, y, z))


def cylinder(x, y, z, radius, height):
    return Part.makeCylinder(radius, height, App.Vector(x, y, z))


def rail(upper):
    y = H - 6.5 if upper else -2.5
    shape = box(0, y, 0, W, 9, 4)
    mounts = [m for m in GEOMETRY['mounts'] if (m['y'] > H / 2) == upper]
    for mount in mounts:
        x, hole_y = mount['x'], mount['y']
        tab_y = hole_y - 3 if upper else 5.5
        tab_end = y + 1 if upper else hole_y + 3
        tab_x, tab_right = max(0, x - 3), min(W, x + 3)
        shape = shape.fuse(box(tab_x, tab_y, 0, tab_right - tab_x, tab_end - tab_y, 4))
        shape = shape.fuse(cylinder(x, hole_y, 4, 1, 1.4))
    outer_y = H + 2.5 if upper else -2.5
    for x in (6, W - 6):
        notch_y = outer_y - 0.85 if upper else outer_y - 0.1
        shape = shape.cut(box(x - 1.1, notch_y, -0.1, 2.2, 0.95, 4.2))
    return shape.removeSplitter()


def carrier():
    length = 2 * W + GAP
    shape = box(-3, -5, 0, length + 6, H + 10, FLOOR)
    for y in (-5, H + 0.4):
        shape = shape.fuse(box(-3, y, FLOOR, length + 6, 4.6, TOP - FLOOR))
    for x0, x1 in ((-3.1, W + 0.2), (W + GAP - 0.2, length + 3.1)):
        for y in (-3, H + 0.4):
            shape = shape.cut(box(x0, y, SLOT_LOW, x1 - x0, 2.6,
                                  SLOT_HIGH - SLOT_LOW))
    shape = shape.fuse(box(W + 1, 0, FLOOR, GAP - 2, H, 5.5))
    for x in (6, length - 6):
        for y in (-3, H + 2.1):
            shape = shape.fuse(box(x - 0.35, y, 18.35, 0.7, 0.9, 1.8))
    return shape.removeSplitter()


doc = App.newDocument("QBF_Reversible_Carrier")
for name, label, shape in (
    ("BumperLower", "Lower edge bumper", rail(False)),
    ("BumperUpper", "Upper edge bumper", rail(True)),
    ("Case", "Two board reversible case", carrier()),
):
    feature = doc.addObject("PartDesign::Feature", name)
    feature.Label = label
    feature.Shape = shape
    feature.addProperty("App::PropertyString", "PrintNote", "Assembly")
    feature.PrintNote = "Print one of each bumper per board; print one case."
    if not shape.isValid():
        raise RuntimeError("Invalid FreeCAD shape: " + name)
doc.recompute()
doc.saveAs(str(ROOT / "QBF_Reversible_Carrier.FCStd"))
